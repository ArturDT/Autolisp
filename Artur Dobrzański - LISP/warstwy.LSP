(vl-load-com)
(setq aplikacja (vlax-get-acad-object))
(vlax-dump-object aplikacja T)
(setq aktywny (vla-get-activedocument aplikacja))
(setq docsC (vla-get-documents aplikacja))
(setq dokument (vla-item docsC 0))
(vlax-dump-object dokument T)
(setq layerC (vla-get-layers dokument))
(vlax-for ilay layerC
   (setq layerL (append layerL (list ilay)))
  )
(setq i 1)
(while (> i -1)
  	(setq i (getint "Podaj nr warstwy (wartosc ujemna zakonczy dzialanie programu): "))
	(setq laymod (nth i layerL))
	(setq sprawdz (vla-get-freeze laymod))
  	(setq tn (getint "zmienic stan zamrozenia warstwy? 0 - nie, inna wartosc - tak: "))
	(if (= tn 0)
		(print "nie zmieniono stanu warstwy")
	  	(if (= sprawdz :vlax-true)	
			(vla-put-freeze laymod "false")
		  	(vla-put-freeze laymod "true")
		)
	 )
  	(setq laymod (nth i layerL)laycolor (vla-get-truecolor laymod))
	(vla-setrgb laycolor
	  	(getint "Podaj R: ")
		(getint "Podaj G: ")
		(getint "Podaj B: ")
	)
  	(vla-put-truecolor laymod laycolor)
)
